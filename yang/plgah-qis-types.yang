module plgah-qis-types {
    yang-version 1;
       
    namespace
      "plgah:qis-types:1_1";

    prefix qis;

    organization "Pascal L.G.A. Heus";

    contact “pascal.heus@gmail.com”;

    description
      "This module contains YANG groupings and data types mirroring the QIS-XML 1.1 specification elements.";

    revision 2016-09-05 {
         description "Draft/Development version";
         reference "QIS-XML: A metadata specification for Quantum Information Science";
    }

    /***********************************************************************
    * REUSABLE TYPES
    ***********************************************************************/

    grouping ComplexNumberType {
        description "A complex number";
        leaf r {
            type decimal64 {fraction-digits 10;}
            default 0;
            description "Real component";
        }
        leaf i {
            type decimal64 {fraction-digits 10;}
            default 0;
            description "Imaginary component";
        }
        list symbolic {
            key "syntax";
            uses SymbolicExpressionType;
            description "Can be used to describe a symbolic expression for this value. 
              When the real and imaginary values are not specified, this can be used for syntax evaluation to infer such values.";
        }
    }

    grouping InputType {
        description "Description of a gate/circuit input";
        leaf number {
            type uint16;
            description "The input number (one based index)";
        }
        uses NameDescType {
            description "Input name and description";
            refine name { mandatory true; }
        }
    }

    grouping IdentificationType {
        description "An entity identifier";
        leaf agency {
            type NcnameType;
            description "A unique identifier for the agency maintaining this entity. Can be inherioted from parent.";
        }
        leaf id {
            type NcnameType;
            mandatory true;
            description "A unique identifier within the container/agency";
        }
        leaf version {
            type VersionType;
            description "The entity version number. Can be inherited from parent.";
        }
        leaf versionDescription {
            type string;
            description "Version rationale / narrative";
        }
    }

    typedef NcnameType {
        type string {
            pattern "[_A-Za-z][_\-A-Za-z0-9.]*";
        }
        description "A resource identifier";
    }
    
    grouping MatrixCellType {
        leaf row {
            type uint32;
            description "The cell row";
        }
        leaf col {
            type uint32;
            description "The cell column";
        }
        uses ComplexNumberType;
        description "A cell representing a complex number in a Matrix";
    }
    
    grouping MatrixType {
        description "A matrix";
        leaf rows {
            type uint32;
            description "The matrix number of rows";
        }
        leaf cols {
            type uint32;
            description "The matrix number of columns";
        }
        list cell {
            key "row col";
            uses MatrixCellType;
            description "A cell in this matrix. Zero valued cells are optional. ";
        }
    }
   
    grouping NameDescType {
        description "A Name and Description";
        leaf name {
            type string;
            description "The entity name";
        }
        leaf description {
            type string;
            description "A detailed description of the entity";
        }
    }

    grouping OutputType {
        description "Description of a gate/circuit output";
        leaf number {
            type uint16;
            description "The output number (one based index)";
        }
        uses NameDescType {
            description "Output name and description";
            refine name { mandatory true; }
        }
    }

    grouping CbitType {
        leaf value {
             type boolean;
             description "The bit value";
        }
        description "A classic bit";
    }

    grouping QubitType {
        container zero {
            uses ComplexNumberType;
            description "The |0> basis state of the Qubit";
        }
        container one {
            uses ComplexNumberType;
            description "The |1> basis state of the Qubit";
        }
        description "A Quantum Bit";
    }

    grouping ReferenceType {
        leaf agency {
            type NcnameType;
            description "The referred resource agency.";
        }
        leaf id {
            type NcnameType;
            mandatory true;
            description "Thr resource identifier within the library/agency";
        }
        leaf version {
            type VersionType;
            description "The resource version number. Can be inherited from parent.";
        }
        leaf library_id {
            type NcnameType;
            description "The identifier of the library containing the resource";
        }
        leaf library_agency {
            type NcnameType;
            description "The library agency, if different from the resource";
        }
        leaf library_version {
            type NcnameType;
            description "The library version, if different from the resource";
        }
        description "A reference to an Identifiable resource";
    }


    grouping SymbolicExpressionType {
        description "Can be used to describe a symbolic expression in various syntaxes";
        leaf value {
            type string;
            mandatory true;
            description "The symbolic expression";
        }
        leaf syntax {
            type string;
            description "The symbolic syntax used for the value";
        }
    }

    grouping TransformationType {
        description "A unitary transformation represented as a square matrix of complex numbers";
        leaf size {
            type uint32;
            description "The matrix n x n size";
        }
        container multiplier {
            uses ComplexNumberType;
            description "A complex number to scale the matrix";
        }
        list cell {
            key "row col";
            uses MatrixCellType;
            description "A cell in this matrix. Zero valued cells are optional. ";
        }       
    }

    typedef VersionType {
        type string {
            pattern "\d|\d\.\d|\d\.\d\.\d";
        }
        description "A version number. Can be n / n.n / n.n.n";
    }

    grouping YangDummyKey {
        description "A YANG dummy key for reuse in lists";
        leaf yang-key {
            type string;
            description "The key value";
        }
    }

    /***********************************************************************
    * GATE
    ***********************************************************************/

    grouping GateType {
        description "A quantum gate";
        uses IdentificationType;
        uses NameDescType {
            refine name { mandatory true; }
        }
        leaf-list nickname {
            type string;
            description "Short/alternate names";
        }
        list input {
            key "number"; 
            uses InputType;
            description "Description of the gate input";
        }
        list output {
            key "number"; 
            uses OutputType;
            description "Description of the gate output";
        }
        list parameter {
            key name;
            uses NameDescType;
            container value {
                uses ComplexNumberType;
                description "The parameter value";
            }
            description "Allows for parameters to be passed to the gate for use in the computation of the Transformation matrix.";
        }
        container transformation { /* required */
            uses TransformationType;
            description "The unitary transformation the gate performs";
        }
    }

    grouping GateLibrary {
        description "A collection of quantum gates";
        uses IdentificationType;
        uses NameDescType;
        list gate {
            key "agency id version";
            uses GateType;
            description "The collection of gates in this libraryr";
        }
    }
    
    /***********************************************************************
     * CIRCUIT
     ***********************************************************************/

    grouping CircuitType {
        description "A quantum circuit";
        uses IdentificationType;
        uses NameDescType {
            refine name { mandatory true; }
        }
        leaf size {
            type uint32;
            description "The circuit size (number of inputs/outputs)";
        }
        list input {
            key "number"; 
            uses InputType;
            description "Description of the gate input";
        }
        list output {
            key "number"; 
            uses OutputType;
            description "Description of the gate output";
        }
        list step {
            key "yang-key";
            uses StepType;
            description "Sequence of steps in this circuit";
        }
    }

    grouping CircuitLibrary {
        description "A collection of quantum circuits";
        uses IdentificationType;
        uses NameDescType;
        list circuit {
            key "agency id version";
            uses CircuitType;
            description "The collection of circuits in this library";
        }
    }

    grouping GateEquivalentCircuitType {
        description "Describes a gate circuit equivalent, typically using univeral gates.";
        container gate-ref {
            uses ReferenceType;
            description "A reference to the Gate the circuit is equivalent to";
        }
        list map {
            key "yang-key";
            description "Collection of maps for this equivalence";
            uses MapType;
        }
        container circuit {
            uses CircuitType;
            description "The circuit equivalent to the Gate/Circuit";
        }
    }
    
    grouping MapType {
        uses YangDummyKey;
        leaf number {
            type uint32;
            description "Maps a wire/qubit/cbit to a circuit/gate input number (one based index)";
        }
        leaf input {
            type uint32;
            description "The input number (one based index)";
        }
        leaf value {
            type boolean;
            mandatory true;
            description "If specified, set the input to a fixed value |0> or |1>.";
        }
        description "Maps circuit wires to gate inputs. If not specified use natural order.";
    }
    
    grouping OperationType {
        uses YangDummyKey;
        leaf reverse {
            type boolean;
            description "If true, indicates that the unitary transformation for this operation should be reversed (dagger/complex conjugate transform)";
        }
        list map {
            key "yang-key";
            description "Collection of maps for this Operation";
            uses MapType;
        }
        choice transform {
            description "The transformation for this operation. Can be a gate, a circuit, or a measurement.";
            case gate-ref {
                container gate-ref {
                    uses ReferenceType;
                    description "A reference to the Gate implementing this Operation";
                }
            }
            case circuit-ref {
                container circuit-ref {
                    uses ReferenceType;
                    description "A reference to the Gate implementing this Operation";
                }
            }
            case measurement {
                leaf measurement {
                    type empty;
                    description "Applies a Measurement on mapped wire(s)";
                }
            }
        }
        description "An operation is a Gate with information mapping qubits or a fixed 0/1 value with the Gat or Circuit inputs";
    }

    grouping StepType {
        description "A execution step in a Circuit";
        uses YangDummyKey;
        uses NameDescType;
        list operation {
            key "yang-key";
            uses OperationType;
            description "The collection of operations for this step";
        }
    }
    
    /***********************************************************************
     * PROGRAM
     ***********************************************************************/

    grouping MemoryType {
        description "Quantum Memory";
        leaf size {
            type uint64;
            description "The memory size";
        }
        uses IdentificationType;
        uses NameDescType;
        uses PrepareType;
        list qubit {
            key "yang-key";
            uses YangDummyKey;
            leaf index {
                type uint64;
                description "The qubit position in memory";
            }
            container value {
                uses ComplexNumberType;
                description "Qubit value";
            }
            description "Qubit value";
        }
    }

    grouping PrepareType {
        description "Prepares/initalizes quantum memory";
        leaf reset {
            type boolean;
            description "Resets all qubits to |0>";
        }
        list qubit-set {
            key "yang-key";
            description "Collection of values to set one or more qubits to";
            uses YangDummyKey;
            choice qubits {
                description "The range of affected qubits";
                case qubit-index {
                    leaf qubit-index {
                        type uint64;
                        description "Sets the qubit as specified memory position";
                    }
                }
                case qubit-range {
                    container qubit-range {
                        leaf start {
                            type uint64;
                            description "Start index position";
                        }
                        leaf end {
                            type uint64;
                            description "End index position";
                        }
                        description "Sets all qubits within specified memory range";
                    }
                }
            }
            container value {
                uses ComplexNumberType;
                description "The value to set the qubit(s) to (can be complex)";
            }
        }
    }

    grouping ProgramType {
        description "A quantum program";
        uses IdentificationType;
        uses NameDescType {
            refine name { mandatory true; }
        }
        container memory {
            uses MemoryType;
            description "Program local allocated quantum memory";
        }
        list register {
            key "agency id version";
            uses RegisterType;
            description "Collection of program level memory register(s)";
        }
        list statement {
            key "yang-key";
            uses YangDummyKey;
            description "The collection of statements";
            choice statement-type {
                description "The choice of statements";
                /* execute statememt */
                case execute {
                    container execute {
                        description "Executes a circuit";
                        choice register-choice {
                            description "The memory local or external register to use. Must match the circuit size";
                            case register {
                                container register {
                                    uses RegisterType;
                                    description "Locally defined register";
                                }
                            }
                            case external-register {
                                container register-ref {
                                    uses ReferenceType;
                                    description "Reference to the external register";
                                }
                            }
                        }
                        choice circuit-choice {
                            description "The local or external circuit to execute";
                            case local-circuit {
                                container circuit {
                                    uses CircuitType;
                                    description "Circuit to execute";
                                }
                            }
                            case external-circuit {
                                container circuit-ref {
                                    uses ReferenceType;
                                    description "Reference to Circuit to execute";
                                }
                            }
                        }
                    }
                }
                /* measure statememt */
                case measure {
                    container measure {
                        choice register-choice {
                            description "The memory register to use";
                            case local-register {
                                container register {
                                    uses RegisterType;
                                    description "Locally defined register";
                                }
                            }
                            case external-register {
                                container register-ref {
                                    uses ReferenceType;
                                    description "Reference to the external register";
                                }
                            }
                        }
                        description "Performs a measurement on register";
                    }
                }
            }
        }
    }

    grouping ProgramLibrary {
        description "A collection of Programs";
        uses IdentificationType;
        uses NameDescType;
        list program {
            key "agency id version";
            uses ProgramType;
            description "The collection of programs in this library";
        }
    }

    grouping RegisterType {
        description "A memory register (subset) to be used for execution. If is hightly recommended for such register to contain an Indentification element (but it could also be referred to by index value). This is somewhat a equivalent of a variable.";
        leaf size {
            type uint64;
            description "The register size";
        }
        uses IdentificationType;
        uses NameDescType;
        container memory-ref {
            uses ReferenceType;
            description "If not using a Program local memory, a reference theto an external memory (global or from another program)";
        }
        /** THIS SECTION NEEDS WORK ***/
        // Not sure how to reflect the XML model. A repeatable choice mixing different element type 
        leaf-list qubit-index {
            type uint64;
            description "Selects a specific qubit in memory";
        }
        list qubit-range {
            key "yang-key";
            uses YangDummyKey;
            leaf start {
                type uint64;
                description "Start index position";
            }
            leaf end {
                type uint64;
                description "End index position";
            }
            description "Selects a range of qubits from memory";
        }
        list register-ref {
            key "agency id version";
            uses ReferenceType;
            description "Include another Register qubits";
        }

        container prepare {
            uses PrepareType;
            description "Prepares/initializes this register";
        }

    }
}
