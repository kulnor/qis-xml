module plgah-qis {
    yang-version 1;
       
    namespace
      "plgah:qis:1_1";

    prefix qis;

    import plgah-qis-types { prefix "qist";  }

    organization "Pascal L.G.A. Heus";

    contact “pascal.heus@gmail.com”;

    description
      "This module is a YANG version of the QIS-XML 1.1 specification.";

    revision 2016-09-04 {
        description "Draft/Development version";
        reference "QIS-XML: A metadata specification for Quantum Information Science";

    }

    container qis {
        description "A QIS instance";
        uses qist:IdentificationType;
        list gate-library {
            key "agency id version";
            uses qist:Gat
	    eLibrary;
            description "Gate libraries available on this device";
        }
        list circuit-library {
            key "agency id version";
            uses qist:CircuitLibrary;
            description "Circuit libraries available on this device";
        }
        list program-library {
            key "agency id version";
            uses qist:ProgramLibrary;
            description "Program libraries available on this device";
        }
	container memory {
	    uses qist:MemoryType;
	    description "Global device memory";
	}
    }
}
