module qis {
    yang-version 1;
       
    namespace
      "qis:1_1";

    prefix r;

    contact 
      “pascal.heus@gmail.com”;

    description
      "This module is a YANG version of the QIS-XML 1.1 specification.";

    revision 2016-09-03 { description "Draft version"; }

    //import ietf-yang-types { prefix yang; }

    /***********************************************************************
    * REUSABLE TYPES & ELEMENTS
    ***********************************************************************/
    
    grouping ComplexNumberType {
        description "A complex number";
        leaf r {
            type decimal64 {fraction-digits 10;}
            default 0;
            description "Real component";
        }
        leaf i {
            type decimal64 {fraction-digits 10;}
            default 0;
            description "Imaginary component";
        }
	list symbolic {
	     key "syntax";
	     uses SymbolicStringType;
        }
    }
    container complex-number {
        uses ComplexNumberType;
    }

    grouping InputType {
        leaf number {
            type uint16;
        }
        uses NameDescType {
            refine name { mandatory true; }
        }
    }
    container input {
        description "A Gate/Circuit Input";
        uses InputType;
    }
    
    grouping IdentificationType {
        leaf id {
	    type string;
	    mandatory true;
	}
        leaf version {
	    type string;
	}
        leaf agency {
	    type string;
	}
    }

    grouping MatrixCellType {
        description "A complex number in a square Matrix";
        leaf row {
            description "The cell row";
            type uint32;
        }
        leaf col {
            description "The cell row";
            type uint32;
        }
        uses ComplexNumberType;
    }
    container matrix-cell {
        uses MatrixCellType;
    }

    grouping MatrixType {
        description "A matrix";
        list cell {
	    key "row col";
            uses MatrixCellType;
        }
    }
    container matrix {
        uses MatrixType;
    }

    grouping NameDescType {
        description "A Name and Description";
        leaf name {
            type string;
        }
        leaf description {
            type string;
        }
    }

    grouping OutputType {
        leaf number {
            type uint16;
        }
        uses NameDescType {
            refine name { mandatory true; }
        }
    }
    container output {
        description "A Gate/Circuit Output";
        uses OutputType;
    }

    grouping QubitType {
        container zero {
	    uses ComplexNumberType;
	}
	container one {
	    uses ComplexNumberType;
	}
    }
    container qubit {
        uses QubitType;
    }

    grouping SymbolicStringType {
        description "Can be used to describe a symbolic expression in various syntaxes";
	leaf value {
	    mandatory true;
	    type string;
	}
	leaf syntax {
	    type string;
	}
    }
    container symbolic-string {
        uses SymbolicStringType;
    }


    /***********************************************************************
    * GATE TYPES & ELEMENTS
    ***********************************************************************/


    
}
